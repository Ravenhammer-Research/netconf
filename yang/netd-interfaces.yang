module netd-interfaces {
  yang-version 1.1;
  namespace "urn:netd:interfaces";
  prefix netd-if;

  organization "NetD Project";
  contact "netd@example.com";
  description "Network interface configuration for NetD";

  revision 2024-01-01 {
    description "Initial version";
  }

  container interfaces {
    description "Interface configuration container";
    
    list interface {
      key "name";
      description "The list of configured interfaces on the device";
      
      leaf name {
        type string;
        description "The name of the interface";
      }
      
      leaf type {
        type string;
        description "The type of the interface";
        default "ethernetCsmacd";
      }
      
      leaf enabled {
        type boolean;
        description "This leaf contains the configured state of the interface";
        default true;
      }
    
    leaf fib {
      type uint32 {
        range "0..255";
      }
      description "FIB (routing table) number for this interface";
      default 0;
    }
      
      container ipv4 {
        description "Parameters for the IPv4 address family";
        
        list address {
          key "ip";
          description "The list of configured IPv4 addresses on the interface";
          
          leaf ip {
            type string;
            description "The IPv4 address on the interface";
          }
          
          leaf prefix-length {
            type uint8 {
              range "0..32";
      }
            description "The length of the subnet prefix";
          }
        }
      }
      
      container ipv6 {
        description "Parameters for the IPv6 address family";
        
        list address {
          key "ip";
          description "The list of configured IPv6 addresses on the interface";
          
          leaf ip {
            type string;
            description "The IPv6 address on the interface";
          }
          
          leaf prefix-length {
            type uint8 {
              range "0..128";
      }
            description "The length of the subnet prefix";
          }
        }
      }
    }
  }
}
