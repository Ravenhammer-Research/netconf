module netd-simple {
  yang-version 1.1;
  namespace "urn:netd:simple";
  prefix netd;

  organization "NetD Project";
  contact "netd@example.com";
  description "Simple network configuration for NetD";

  revision 2024-01-01 {
    description "Initial version";
  }

  typedef ipv4-address {
    type string {
      pattern '^(([0-9]|[1-9][0-9]|1[0-9][0-9]|2[0-4][0-9]|25[0-5])\.){3}([0-9]|[1-9][0-9]|1[0-9][0-9]|2[0-4][0-9]|25[0-5])$';
    }
    description "IPv4 address in dotted decimal notation";
  }

  typedef ipv6-address {
    type string;
    description "IPv6 address";
  }

  typedef ip-prefix {
    type string;
    description "IP prefix in CIDR notation";
  }

  container netd-config {
    description "NetD configuration";
    
    list interface {
      key "name";
      description "Network interface configuration";
      
      leaf name {
        type string;
        description "Interface name";
      }
      
      leaf enabled {
        type boolean;
        default true;
        description "Interface enabled state";
      }
      
      leaf fib {
        type uint32 {
          range "0..255";
        }
        default 0;
        description "FIB (routing table) number";
      }
      
      list address {
        key "ip";
        description "IP address configuration";
        
        leaf ip {
          type ip-prefix;
          description "IP address with prefix length";
        }
        
        leaf family {
          type enumeration {
            enum ipv4;
            enum ipv6;
          }
          mandatory true;
          description "Address family";
        }
      }
    }
    
    list route {
      key "destination";
      description "Static route configuration";
      
      leaf destination {
        type ip-prefix;
        description "Destination network";
      }
      
      leaf gateway {
        type union {
          type ipv4-address;
          type ipv6-address;
        }
        mandatory true;
        description "Gateway address";
      }
      
      leaf fib {
        type uint32 {
          range "0..255";
        }
        default 0;
        description "FIB (routing table) number";
      }
      
      leaf description {
        type string;
        description "Route description";
      }
    }
  }
}
