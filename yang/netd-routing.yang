module netd-routing {
  yang-version 1.1;
  namespace "urn:netd:routing";
  prefix netd-rt;

  organization "NetD Project";
  contact "netd@example.com";
  description "Routing configuration for NetD";

  revision 2024-01-01 {
    description "Initial version";
  }

  container routing {
    description "Routing configuration container";
    
    container routing-instance {
      description "Default routing instance";
      
      leaf name {
        type string;
        description "Routing instance name";
        default "default";
      }
      
      container routing-protocols {
        description "Routing protocols container";
        
        container routing-protocol {
          description "Static routing protocol";
          
          leaf type {
            type string;
            description "Routing protocol type";
            default "static";
          }
    
          container static-routes {
            description "Static routes configuration";
      
      list route {
              key "destination-prefix";
        description "Static route entry";
        
              leaf destination-prefix {
                type string;
                description "Destination network prefix (e.g., 192.168.1.0/24)";
        }
              
              container next-hop {
                description "Next hop configuration";
        
                leaf next-hop-address {
                  type string;
                  description "Next hop IP address";
                }
        }
        
        leaf fib {
          type uint32 {
            range "0..255";
          }
          description "FIB (routing table) number for this route";
          default 0;
        }
            }
          }
        }
      }
    }
  }
}
